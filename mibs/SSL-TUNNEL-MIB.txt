SSL-TUNNEL-MIB DEFINITIONS ::= BEGIN

IMPORTS
    MODULE-IDENTITY, OBJECT-TYPE, Counter64,
    Integer32, Gauge32, enterprises
        FROM SNMPv2-SMI
    DisplayString
        FROM SNMPv2-TC;

sslTunnelMIB MODULE-IDENTITY
    LAST-UPDATED "202501280000Z"
    ORGANIZATION "SSSonector Project"
    CONTACT-INFO
        "Email: support@example.com"
    DESCRIPTION
        "MIB for monitoring SSL tunnel metrics"
    REVISION "202501280000Z"
    DESCRIPTION
        "Initial version"
    ::= { enterprises 2021 10 }

sslTunnelObjects OBJECT IDENTIFIER ::= { sslTunnelMIB 1 }
sslTunnelStats   OBJECT IDENTIFIER ::= { sslTunnelObjects 3 }

-- Network Metrics

bytesReceived OBJECT-TYPE
    SYNTAX      Counter64
    MAX-ACCESS  read-only
    STATUS      current
    DESCRIPTION
        "Total number of bytes received through the tunnel"
    ::= { sslTunnelStats 1 }

bytesSent OBJECT-TYPE
    SYNTAX      Counter64
    MAX-ACCESS  read-only
    STATUS      current
    DESCRIPTION
        "Total number of bytes sent through the tunnel"
    ::= { sslTunnelStats 2 }

packetsLost OBJECT-TYPE
    SYNTAX      Counter64
    MAX-ACCESS  read-only
    STATUS      current
    DESCRIPTION
        "Total number of packets lost during transmission"
    ::= { sslTunnelStats 3 }

latency OBJECT-TYPE
    SYNTAX      Integer32
    UNITS       "microseconds"
    MAX-ACCESS  read-only
    STATUS      current
    DESCRIPTION
        "Current tunnel latency in microseconds"
    ::= { sslTunnelStats 4 }

-- System Metrics

uptime OBJECT-TYPE
    SYNTAX      Integer32
    UNITS       "seconds"
    MAX-ACCESS  read-only
    STATUS      current
    DESCRIPTION
        "Time in seconds since the tunnel was started"
    ::= { sslTunnelStats 5 }

cpuUsage OBJECT-TYPE
    SYNTAX      DisplayString
    MAX-ACCESS  read-only
    STATUS      current
    DESCRIPTION
        "Current CPU usage percentage"
    ::= { sslTunnelStats 6 }

memoryUsage OBJECT-TYPE
    SYNTAX      DisplayString
    MAX-ACCESS  read-only
    STATUS      current
    DESCRIPTION
        "Current memory usage percentage"
    ::= { sslTunnelStats 7 }

-- Connection Metrics

activeConnections OBJECT-TYPE
    SYNTAX      Gauge32
    MAX-ACCESS  read-only
    STATUS      current
    DESCRIPTION
        "Current number of active tunnel connections"
    ::= { sslTunnelStats 8 }

totalConnections OBJECT-TYPE
    SYNTAX      Counter64
    MAX-ACCESS  read-only
    STATUS      current
    DESCRIPTION
        "Total number of tunnel connections since startup"
    ::= { sslTunnelStats 9 }

END
